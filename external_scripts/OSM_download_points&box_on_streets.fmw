FME workspace OSM_download_points&box_on_streets.fmw

Parameters:
- DestDataset_GEOJSON = $(FME_MF_DIR)FR_Export_Points_on_Highway.json   # Destination GeoJSON File
- DestDataset_GEOJSON_5 = $(FME_MF_DIR)FR_Export_Box_on_Highway.json   # Destination GeoJSON File

Writers:
- GEOJSON_3: GEOJSON to $(DestDataset_GEOJSON) in EPSG:3035
- GEOJSON_1: GEOJSON to $(DestDataset_GEOJSON_5) in EPSG:3035

Creator
    GEOMTYPE = Geometry Object
    NUM = 1
    CREATED -> TempPathnameCreator_2
TempPathnameCreator_2
    EXTENSION = .osm
    PATHNAME_ATTR = _pathname
    -> HTTPCaller_3
    -> HTTPCaller_2
    -> HTTPCaller_4
Note: DE
HTTPCaller_2 [off]
    CONNECTION_TIMEOUT_LENGTH = 60
    CONTENT_TYPE_LOOKUP = text/plain
    ERROR_ATTR = _error
    FILE_PATH_ATTR = _response_file_path
    FOLLOW_REDIRECTS = Yes
    HTTP_METHOD = POST
    OUTPUT_FILENAME = @Value(_pathname)
    SAVE_FILE_LOOKUP = YES
    SAVE_MULTI = No
    STATUS_CODE_ATTR = _http_status_code
    TARGET_URL = http://overpass-api.de/api/interpreter
    TRANSFER_TIMEOUT_LENGTH = 90
    UPLOAD_BODY:
      data=way["highway"="motorway"](47.270,5.866,55.099,15.042);
      (._;>;);
      out;
    UPLOAD_TYPE = Specify Upload Body
    USE_COOKIES = No
    VERIFY_SSL_CERTIFICATES = Yes
    SAVE_FILE = File
    UPLOAD_CONTENT_TYPE = Text (text/plain)
    -> FeatureReader_5 [INITIATOR]
Note: CH
HTTPCaller_3 [off]
    CONNECTION_TIMEOUT_LENGTH = 60
    CONTENT_TYPE_LOOKUP = text/plain
    ERROR_ATTR = _error
    FILE_PATH_ATTR = _response_file_path
    FOLLOW_REDIRECTS = Yes
    HTTP_METHOD = POST
    OUTPUT_FILENAME = @Value(_pathname)
    SAVE_FILE_LOOKUP = YES
    SAVE_MULTI = No
    STATUS_CODE_ATTR = _http_status_code
    TARGET_URL = http://overpass-api.de/api/interpreter
    TRANSFER_TIMEOUT_LENGTH = 90
    UPLOAD_BODY:
      data=way["highway"="motorway"](45.817,5.955,47.808,10.492);
      (._;>;);
      out;
    UPLOAD_TYPE = Specify Upload Body
    USE_COOKIES = No
    VERIFY_SSL_CERTIFICATES = Yes
    SAVE_FILE = File
    UPLOAD_CONTENT_TYPE = Text (text/plain)
    -> FeatureReader_5 [INITIATOR]
Note: FR
HTTPCaller_4
    CONNECTION_TIMEOUT_LENGTH = 60
    CONTENT_TYPE_LOOKUP = text/plain
    ERROR_ATTR = _error
    FILE_PATH_ATTR = _response_file_path
    FOLLOW_REDIRECTS = Yes
    HTTP_METHOD = POST
    OUTPUT_FILENAME = @Value(_pathname)
    SAVE_FILE_LOOKUP = YES
    SAVE_MULTI = No
    STATUS_CODE_ATTR = _http_status_code
    TARGET_URL = http://overpass-api.de/api/interpreter
    TRANSFER_TIMEOUT_LENGTH = 90
    UPLOAD_BODY:
      data=way["highway"="motorway"](41.303,-5.142,51.124,9.561);
      (._;>;);
      out;
    UPLOAD_TYPE = Specify Upload Body
    USE_COOKIES = No
    VERIFY_SSL_CERTIFICATES = Yes
    SAVE_FILE = File
    UPLOAD_CONTENT_TYPE = Text (text/plain)
    -> FeatureReader_5 [INITIATOR]
FeatureReader_5
    ATTR_ACCUM_MODE = Only Use Result
    COMBINE_GEOM = Use Result
    DATASET = @Value(_response_file_path)
    FORMAT = OSM
    INTERACT = <No Spatial Filter>
    OSM_ALLOW_DUPLICATE_COORDINATES = no
    OSM_BUILD_MULTIPOLYGON_RELATION = no
    OSM_CACHE_WAYS_AND_RELATIONS = no
    OSM_COMMUNITY_FEATURE_TYPES = MAPPED
    OSM_HANDLE_MULTI = SELECT_FIRST
    OSM_OUTPUT_INCOMPLETE_WAYS_AND_RELATIONS = no
    OSM_REMOVE_NODE_LIST = no
    OSM_SCAN_ALL_FEATURES_FOR_SCHEMA = no
    OSM_USER_CONFIG = NO
    OSM_USE_SEARCH_ENVELOPE = NO
    OUTPUT_FEATURES_DISPLAY = Schema and Data Features
    <OTHER> -> GeometryFilter
AttributeKeeper
    CREATE_BULK_MODE_FEATURES = NO
    -> Reprojector
Reprojector
    DEST = EPSG:3035
    INTERPOLATION_TYPE = NearestNeighbor
    RASTER_CELL_SIZE = PreserveCells
    RASTER_TOLERANCE = 0.0
    SOURCE = EPSG:4326
    REPROJECTED -> Bufferer
    REPROJECTED -> Reprojector_Reprojected
Note: Schliessen von Lücken -- ist das sinnvoll? - Ich denke ja
Snapper
    EXTEND_LINES = NEVER
    SAVE_SHORT_LINES = No
    SNAPTYPE = END_NODE
    TOLERANCE = 1000
    SNAPPED -> Snapper_Snapped
    SNAPPED -> LineDivider [Line]
    UNTOUCHED -> Snapper_Untouched
    UNTOUCHED -> LineDivider [Line]
LineDivider
    DIM = 2D
    MODE = ToLength
    OUTPUT = LinesAndPoints
    VALUE = 1000
    Line -> LineDivider_Line
    Point -> LineDivider_Point
    Point -> Bufferer_2
    Point -> Points_Highway (writer GEOJSON_3)
Points_Highway (writer GEOJSON_3)
    attributes: _part_number string, _geometry_label string
Bufferer_2
    ANGLE = 22.5
    CAP_STYLE_LOOKUP = CAP_PROJECTING
    CORNER_STYLE_LOOKUP = JOIN_ARC
    MODE = AREA
    OFFSET = 640
    OFFSET_UNITS = METERS
    PRECISION = EXACT
    CAP_STYLE = Square
    CORNER_STYLE = Arc
    BUFFERED -> BoundingBoxReplacer_Box
    BUFFERED -> Box_Highway (writer GEOJSON_1)
Box_Highway (writer GEOJSON_1)
    attributes: _part_number string, _geometry_label string

Bookmark: Wenn die Anfrage besser wäre, bräuchte es das nicht
GeometryFilter
    FILTER_MODE = SIMPLE
    FILTER_MULTI = FILTER_TYPES]Line]FILTER_TYPES_Simple]Line
    FILTER_TYPES = Line
    FILTER_TYPES_Simple = Line
    Curve -> AttributeExposer_2

Bookmark: Keine Tunnel
AttributeExposer_2
    ATTR_TABLE = tunnel,
    -> Tester
Tester
    BOOL_OP = OR
    TEST_CLAUSE = TEST @Value(tunnel) != yes
    TEST_MODE = TEST
    PASSED -> AttributeKeeper

Bookmark: Geometrische Berenigung aneinanderliegender Strassen
Bufferer
    ANGLE = 22.5
    CAP_STYLE_LOOKUP = CAP_ARC
    CORNER_STYLE_LOOKUP = JOIN_ARC
    MODE = AREA
    OFFSET = 100
    OFFSET_UNITS = NONE
    PRECISION = APPROX
    CAP_STYLE = Arc
    CORNER_STYLE = Arc
    BUFFERED -> Dissolver
Dissolver
    ACCUM_INPUT_ATTRS_LOOKUP = One
    CLEANING_TOLERANCE_LOOKUP = AUTO
    CONNECT_Z_MODE_LOOKUP = FIRST_WINS
    DEAGGREGATE_INPUT = Yes
    ACCUM_INPUT_ATTRS = Use Attributes From One Feature
    CLEANING_TOLERANCE = Automatic
    CONNECT_Z_MODE = First Wins
    AREA -> CenterlineReplacer
CenterlineReplacer
    MODE = APPROX_CENTER_LINE
    CENTERLINE -> Deaggregator
    CENTERLINE -> CenterlineReplacer_Centerline
Deaggregator
    ATTR_ACCUM_MODE = HANDLE_CONFLICT
    ATTR_CONFLICT_RES = INCOMING_IF_CONFLICT
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> Snapper
    DEAGGREGATED -> Deaggregator_Deaggregated

Bookmark: End-Kontrolle
BoundingBoxReplacer_Box: Inspector [off]
LineDivider_Line: Inspector [off]
LineDivider_Point: Inspector [off]

Bookmark: Kontrollen
Snapper_Snapped: Inspector [off]
Snapper_Untouched: Inspector [off]
Deaggregator_Deaggregated: Inspector [off]
CenterlineReplacer_Centerline: Inspector [off]
Reprojector_Reprojected: Inspector [off]

FME custom transformer LineDivider
Divides a line into multiple lines. Resulting lines and/or points which separate the lines will be output.
Every output feature will hold all the attributes of the original feature.
This transformer accepts non-aggregate Curve (Line, Arc or Path) features only.
If an input feature has other type geometry or does not have geometry, it will be output from the <Rejected> port.
Similar functions have been provided by the IterativeSnipper_2013 and the DistanceMarker_2013 in the FME Hub.
Major differences from them are:
1) Integrated their functions so that divided lines and distance markers can be created efficiently at the same time, but users still can also use each function separately. See the "Output" parameter.
2) Added "Measurement Mode" parameter so that users can choose 2D or 3D for measuring lengths.
3) Implemented with a Python script to improve performance, although the algorithm is basically same as theirs.
Parameters
Measurement Mode:
By default, the transformer measures lengths in 2D, but you can change it to 3D with this parameter setting.
Dividing Mode:
Choose one of these modes.
"Shorten to Following Length"
- snips iteratively each input line from its head by the length specified to the "Line Length or Number of Lines" parameter. Length of the final line could be less than the specified length.
"Shorten to Approximately Following Length"
- divides each input line into multiple lines having identical length which is approximately equal to the length specified to the "Line Length or Number of Lines" parameter.
"Divide to Following Number of Lines"
- divides each input line into multiple lines having identical length by the number specified to the "Line Length or Number of Lines" parameter.
Line Length or Number of Lines:
Specify a numeric value if you set "Shorten to Following Length" or "Shorten to Approximately Following Length" in the "Dividing Mode" parameter.
Specify an integer number if you set "Divide to Following Number of Lines" in the "Dividing Mode" parameter.
In both cases, the value must be greater than 0.
Output:
You can control what kind of features should be output with this parameter setting.
By default, the transformer outputs both Lines and Points, but you could run it more efficiently by selecting a preferable option if you need either only Lines or Points.
"Lines"
- outputs divided lines only. Nothing is output from the Point port.
"Lines and Points" (default)
- outputs both divided lines and points which separate the lines; including start and end nodes of the original line.
"Lines and Points except Start and End Nodes"
- outputs both divided lines and points which separate the lines; excluding start and end nodes of the original line.
"Points"
- outputs points only; including start and end nodes of the original line. Nothing is output from the Line port.
"Points except Start and End Nodes"
- outputs points only; excluding start and end nodes of the original line. Nothing is output from the Line port.

Parameters:
- DIM = 2D   # Measurement Mode
- MODE = ToLength
- VALUE =   # Line Length or Number of Lines
- OUTPUT = LinesAndPoints

Line (input)
    -> AggregateFilter
AggregateFilter
    AGGREGATE -> <Rejected> (output)
    NOT_AGGREGATE -> GeometryFilter
GeometryFilter
    BREAK_AGG_BOOL = 0
    GEOM_PORTS = LINE ARC
    BREAK_AGG = No
    GEOM_PORT_NAMES = Line Arc
    LINE -> AttributeCreator
    ARC -> AttributeCreator
    <UNFILTERED> -> <Rejected> (output)
AttributeCreator
    ATTR_LIST = __linedivider.dim,$(DIM),__linedivider.mode,$(MODE),__linedivider.value,@Evaluate($(VALUE)),__linedivider.output,$(OUTPUT)
    -> PythonCaller
PythonCaller
    HIDE_ATTRIBUTES = __linedivider.dim __linedivider.mode __linedivider.value __linedivider.output
    PYTHONSOURCE:
      # 2014-11-15, Takashi Iijima, Original Implementation
      # 2015-05-11, Takashi Iijima, Added Arc support; Fixed a problem on creating interval points of Path
      # 2017-06-26, Takashi Iijima, Updated to improve robustness.
      # 2020-01-12, Takashi Iijima, Changed Default Python Interpreter to 3.6+, saved with FME 2017.1.2.1

      import fmeobjects, math

      class LineDivider(object):
          def input(self, feature):
              is3D = (feature.getAttribute('__linedivider.dim') == '3D')
              mode = feature.getAttribute('__linedivider.mode')
              value = float(feature.getAttribute('__linedivider.value'))
              output = feature.getAttribute('__linedivider.output')
              for attr in ['dim', 'mode', 'value', 'output']:
                  feature.removeAttribute('__linedivider.' + attr)

              coordSys = feature.getCoordSys()
              outputLines = output.startswith('Lines')
              outputPoints = output.startswith('LinesAndPoints') or output.startswith('Points')
              outputEndNodes = outputPoints and not output.endswith('ExceptEndNodes')

              # Get original curve geometry
              curve = feature.getGeometry()
              length = curve.getLength(is3D)
              numLines = int(round(value) if mode == 'ToNumber' else math.ceil(length / value))
              len = value if mode == 'ToLength' else length / numLines

              for n, (beg, end) in enumerate([(i*len, (i+1)*len) for i in range(numLines)], 1):
                  # Snip the original curve
                  if n == numLines:
                      end = -1
                  curve.snip(fmeobjects.SNIP_DISTANCE, is3D, beg, end)

                  if outputLines:
                      line = feature.cloneAttributes()
                      line.setGeometry(curve)
                      line.setCoordSys(coordSys)
                      self.pyoutput(line)

                  if outputPoints and (0.0 < beg or outputEndNodes):
                      point = feature.cloneAttributes()
                      point.setGeometry(curve.getStartPoint())
                      point.setCoordSys(coordSys)
                      self.pyoutput(point)

                  # Restore original curve geometry
                  curve = feature.getGeometry()

              if outputEndNodes:
                  point = feature.cloneAttributes()
                  point.setGeometry(curve.getEndPoint())
                  point.setCoordSys(coordSys)
                  self.pyoutput(point)
    PYTHONSYMBOL = LineDivider
    -> GeometryFilter_2
GeometryFilter_2
    BREAK_AGG_BOOL = 0
    GEOM_PORTS = POINT LINE ARC
    BREAK_AGG = No
    GEOM_PORT_NAMES = Point Line Arc
    POINT -> Point (output)
    LINE -> Line (output)
    ARC -> Line (output)
Line (output)
Point (output)
<Rejected> (output)
