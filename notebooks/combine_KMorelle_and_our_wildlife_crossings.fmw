FME workspace combine_KMorelle_and_our_wildlife_crossings.fmw

Parameters:
- SourceDataset_OGCGEOPACKAGE = $(FME_MF_DIR)training_data_digitized_wildlife_crossings.gpkg   # GeoPackage File
- SourceDataset_SHAPEFILE = ""$(FME_MF_DIR)wildlife_crossings_polygons_and_points\wildlife_crossing_points_Brennan.shp" "$(FME_MF_DIR)wildlife_crossings_polygons_and_points\wildlife_crossing_polygons.shp""   # Source Esri Shapefile(s)
- DestDataset_GEOJSON_3 = $(FME_MF_DIR)wildlife_crossings_polygons_and_points\KMorelle_and_us_wildlife_poly_bridges.json   # Destination GeoJSON File
- DestDataset_GEOJSON = $(FME_MF_DIR)wildlife_crossings_polygons_and_points\KMorelle_wildlife_poly_bridges.json   # Destination GeoJSON File
- SourceDataset_FILEGDB = $(FME_MF_DIR)hoheitsgrenze-landesvermessung_2056\hoheitsgrenze-landesvermessung_2056.gdb   # File Geodatabase

Readers:
- OGCGEOPACKAGE_1: OGCGEOPACKAGE from $(SourceDataset_OGCGEOPACKAGE)
- SHAPEFILE_1: SHAPEFILE from $(SourceDataset_SHAPEFILE)
- FILEGDB_1: FILEGDB from $(SourceDataset_FILEGDB)

Writers:
- GEOJSON_2: GEOJSON to $(DestDataset_GEOJSON) in EPSG:3035
- GEOJSON_1: GEOJSON to $(DestDataset_GEOJSON_3) in EPSG:3035

wildlife_crossing_points_Brennan (reader SHAPEFILE_1)
    attributes: Name varchar(254), descriptio varchar(254), timestamp varchar(24), begin varchar(24), end varchar(24), altitudeMo varchar(254), tessellate long, extrude long, visibility long, drawOrder long, icon varchar(254), country varchar(254), year varchar(254), estimated_ varchar(254), w_using_in varchar(254), lanes varchar(254), railway_sp varchar(254), continent varchar(254), estimate_1 varchar(254), estimate_2 varchar(254), state_prov varchar(254), name_if_ap varchar(254), overpass_o varchar(254), targeted_s varchar(254), approx_siz varchar(254), price varchar(254), year_of_bu varchar(254), known_widt varchar(254), width varchar(254), known_leng varchar(254),
      length varchar(254), w_l_ratio_ varchar(254), x39 varchar(254)
    -> Reprojector
wildlife_crossing_polygons (reader SHAPEFILE_1)
    attributes: osm_id varchar(80), name varchar(80), CDOT_rt varchar(80), NHS varchar(80), access varchar(80), alt_nam varchar(80), animal varchar(80), area varchar(80), barrier varchar(80), bicycle varchar(80), boat varchar(80), boundry varchar(80), bridge varchar(80), brdg_st varchar(80), b__2015 varchar(80), buildng varchar(80), cnstrct varchar(80), dscrptn varchar(80), dscrptn_d varchar(80), dscrptn_n varchar(80), destntn varchar(80), diametr varchar(80), dssd_br varchar(80), dssd_hg varchar(80), dssd_ly varchar(80), elctrfd varchar(80), embnkmn varchar(80), exprssw varchar(80), fence varchar(80), fixme varchar(80),
      foot varchar(80), for_txn varchar(80), freqncy varchar(80), gauge varchar(80), height varchar(80), hgv varchar(80), hgv_nt_ varchar(80), highspd varchar(80), highway varchar(80), horse varchar(80), image varchar(80), informl varchar(80), int_ref varchar(80), intrmtt varchar(80), landcvr varchar(80), landuse varchar(80), lanes varchar(80), layer varchar(80), lef_typ varchar(80), length varchar(80), level varchar(80), lit varchar(80), loc_nam varchar(80), locatin varchar(80), man_mad varchar(80), mapllry varchar(80), materil varchar(80), maxhght varchar(80), maxsped varchar(80), mxwght_ varchar(80),
      mtr_vhc varchar(80), motorcr varchar(80), mtrcycl varchar(80), motorrd varchar(80), mtb_scl varchar(80), name_de varchar(80), name_en varchar(80), name_fr varchar(80), name_ja varchar(80), name_ko varchar(80), name_nn varchar(80), name_nl varchar(80), name_zh varchar(80), nm_zh_Hns varchar(80), nm_zh_Hnt varchar(80), name_1 varchar(80), name_2 varchar(80), natural varchar(80), note varchar(254), nt_Bstl varchar(80), nt_Bwrk varchar(80), ntStrßn varchar(80), nt_tnnl varchar(80), obsolet varchar(80), offcl_n varchar(80), old_nam varchar(80), oneway varchar(80), operatr varchar(80), pssngr_ varchar(80), railway varchar(80),
      rlwy_tc varchar(80), rlwy_t_ varchar(80), ref varchar(80), r_FR_SN varchar(80), ruins varchar(80), segrgtd varchar(80), signals varchar(80), size varchar(80), smthnss varchar(80), source varchar(121), sorc_dt varchar(80), src_ggr varchar(80), src_gmt varchar(80), src_h__ varchar(80), strt_dt varchar(80), surface varchar(80), srvy_dt varchar(80), tgr_cnt varchar(80), toll varchar(80), tracks varchar(80), trcktyp varchar(80), trl_vsb varchar(80), tunnel varchar(80), tnnl_ln varchar(80), tnnl_nm varchar(80), tnnl_rf varchar(80), url varchar(80), usage varchar(80), vehicle varchar(80), voltage varchar(80),
      wall varchar(80), waterwy varchar(80), website varchar(80), width varchar(80), wikidat varchar(80), wkmd_cm varchar(80), wikiped varchar(80), wldlf_c varchar(80), yr_f_cn varchar(80)
    -> Reprojector
Reprojector
    DEST = EPSG:3035
    INTERPOLATION_TYPE = NearestNeighbor
    RASTER_CELL_SIZE = PreserveCells
    RASTER_TOLERANCE = 0.0
    REPROJECTED -> GeometryFilter
GeometryFilter
    FILTER_MODE = SIMPLE
    FILTER_MULTI = FILTER_TYPES]Area]FILTER_TYPES_Simple]Area
    FILTER_TYPES = Area
    FILTER_TYPES_Simple = Area
    Area -> GeometryExtractor
PointOnAreaOverlayer
    ATTR_ACCUM_MODE = HANDLE_CONFLICT
    ATTR_CONFLICT_RES = ORIGINAL_IF_CONFLICT
    DEAGGREGATE_INPUT = Yes
    OV_ATTR = _overlaps
    POLYS_FIRST = NO
    POINT -> Tester
Tester
    BOOL_OP = OR
    TEST_CLAUSE = TEST @Value(europa) = yes
    TEST_MODE = TEST
    PASSED -> GeometryReplacer
Note: OriginalGeometrie zurückstellen
GeometryReplacer
    KIND = fmebinary
    REMOVE_ATTRIBUTE = Yes
    SOURCE = @Value(_geometry)
    KIND_LONG = FME Binary
    -> AttributeManager
AttributeManager
    ATTR_TABLE:
      REMOVE Name (varchar(254))
      REMOVE descriptio (varchar(254))
      REMOVE timestamp (varchar(24))
      REMOVE begin (varchar(24))
      REMOVE end (varchar(24))
      REMOVE altitudeMo (varchar(254))
      REMOVE tessellate (int32)
      REMOVE extrude (int32)
      REMOVE visibility (int32)
      REMOVE drawOrder (int32)
      REMOVE icon (varchar(254))
      REMOVE country (varchar(254))
      REMOVE year (varchar(254))
      REMOVE estimated_ (varchar(254))
      REMOVE w_using_in (varchar(254))
      REMOVE lanes (varchar(254))
      REMOVE railway_sp (varchar(254))
      REMOVE continent (varchar(254))
      REMOVE estimate_1 (varchar(254))
      REMOVE estimate_2 (varchar(254))
      REMOVE state_prov (varchar(254))
      REMOVE name_if_ap (varchar(254))
      REMOVE overpass_o (varchar(254))
      REMOVE targeted_s (varchar(254))
      REMOVE approx_siz (varchar(254))
      REMOVE price (varchar(254))
      REMOVE year_of_bu (varchar(254))
      REMOVE known_widt (varchar(254))
      REMOVE width (varchar(254))
      REMOVE known_leng (varchar(254))
      REMOVE length (varchar(254))
      REMOVE w_l_ratio_ (varchar(254))
      REMOVE x39 (varchar(254))
      REMOVE name (varchar(80))
      REMOVE CDOT_rt (varchar(80))
      REMOVE NHS (varchar(80))
      REMOVE access (varchar(80))
      REMOVE alt_nam (varchar(80))
      REMOVE animal (varchar(80))
      REMOVE area (varchar(80))
      REMOVE barrier (varchar(80))
      REMOVE bicycle (varchar(80))
      REMOVE boat (varchar(80))
      REMOVE boundry (varchar(80))
      REMOVE brdg_st (varchar(80))
      REMOVE b__2015 (varchar(80))
      REMOVE buildng (varchar(80))
      REMOVE cnstrct (varchar(80))
      REMOVE dscrptn (varchar(80))
      REMOVE dscrptn_d (varchar(80))
      REMOVE dscrptn_n (varchar(80))
      REMOVE destntn (varchar(80))
      REMOVE diametr (varchar(80))
      REMOVE dssd_br (varchar(80))
      REMOVE dssd_hg (varchar(80))
      REMOVE dssd_ly (varchar(80))
      REMOVE elctrfd (varchar(80))
      REMOVE embnkmn (varchar(80))
      REMOVE exprssw (varchar(80))
      REMOVE fence (varchar(80))
      REMOVE fixme (varchar(80))
      REMOVE foot (varchar(80))
      REMOVE for_txn (varchar(80))
      REMOVE freqncy (varchar(80))
      REMOVE gauge (varchar(80))
      REMOVE height (varchar(80))
      REMOVE hgv (varchar(80))
      REMOVE hgv_nt_ (varchar(80))
      REMOVE highspd (varchar(80))
      REMOVE highway (varchar(80))
      REMOVE horse (varchar(80))
      REMOVE image (varchar(80))
      REMOVE informl (varchar(80))
      REMOVE int_ref (varchar(80))
      REMOVE intrmtt (varchar(80))
      REMOVE landcvr (varchar(80))
      REMOVE landuse (varchar(80))
      REMOVE layer (varchar(80))
      REMOVE lef_typ (varchar(80))
      REMOVE level (varchar(80))
      REMOVE lit (varchar(80))
      REMOVE loc_nam (varchar(80))
      REMOVE locatin (varchar(80))
      REMOVE man_mad (varchar(80))
      REMOVE mapllry (varchar(80))
      REMOVE materil (varchar(80))
      REMOVE maxhght (varchar(80))
      REMOVE maxsped (varchar(80))
      REMOVE mxwght_ (varchar(80))
      REMOVE mtr_vhc (varchar(80))
      REMOVE motorcr (varchar(80))
      REMOVE mtrcycl (varchar(80))
      REMOVE motorrd (varchar(80))
      REMOVE mtb_scl (varchar(80))
      REMOVE name_de (varchar(80))
      REMOVE name_en (varchar(80))
      REMOVE name_fr (varchar(80))
      REMOVE name_ja (varchar(80))
      REMOVE name_ko (varchar(80))
      REMOVE name_nn (varchar(80))
      REMOVE name_nl (varchar(80))
      REMOVE name_zh (varchar(80))
      REMOVE nm_zh_Hns (varchar(80))
      REMOVE nm_zh_Hnt (varchar(80))
      REMOVE name_1 (varchar(80))
      REMOVE name_2 (varchar(80))
      REMOVE natural (varchar(80))
      REMOVE note (varchar(254))
      REMOVE nt_Bstl (varchar(80))
      REMOVE nt_Bwrk (varchar(80))
      REMOVE ntStrßn (varchar(80))
      REMOVE nt_tnnl (varchar(80))
      REMOVE obsolet (varchar(80))
      REMOVE offcl_n (varchar(80))
      REMOVE old_nam (varchar(80))
      REMOVE oneway (varchar(80))
      REMOVE operatr (varchar(80))
      REMOVE pssngr_ (varchar(80))
      REMOVE railway (varchar(80))
      REMOVE rlwy_tc (varchar(80))
      REMOVE rlwy_t_ (varchar(80))
      REMOVE ref (varchar(80))
      REMOVE r_FR_SN (varchar(80))
      REMOVE ruins (varchar(80))
      REMOVE segrgtd (varchar(80))
      REMOVE signals (varchar(80))
      REMOVE size (varchar(80))
      REMOVE smthnss (varchar(80))
      REMOVE source (varchar(121))
      REMOVE sorc_dt (varchar(80))
      REMOVE src_ggr (varchar(80))
      REMOVE src_gmt (varchar(80))
      REMOVE src_h__ (varchar(80))
      REMOVE strt_dt (varchar(80))
      REMOVE surface (varchar(80))
      REMOVE srvy_dt (varchar(80))
      REMOVE tgr_cnt (varchar(80))
      REMOVE toll (varchar(80))
      REMOVE tracks (varchar(80))
      REMOVE trcktyp (varchar(80))
      REMOVE trl_vsb (varchar(80))
      REMOVE tunnel (varchar(80))
      REMOVE tnnl_ln (varchar(80))
      REMOVE tnnl_nm (varchar(80))
      REMOVE tnnl_rf (varchar(80))
      REMOVE url (varchar(80))
      REMOVE usage (varchar(80))
      REMOVE vehicle (varchar(80))
      REMOVE voltage (varchar(80))
      REMOVE wall (varchar(80))
      REMOVE waterwy (varchar(80))
      REMOVE website (varchar(80))
      REMOVE wikidat (varchar(80))
      REMOVE wkmd_cm (varchar(80))
      REMOVE wikiped (varchar(80))
      REMOVE wldlf_c (varchar(80))
      REMOVE yr_f_cn (varchar(80))
      REMOVE europa (varchar(3))
      REMOVE _creation_instance (uint64)
      REMOVE _overlaps (uint32)
    -> Tester_2
Tester_2
    BOOL_OP = OR
    TEST_CLAUSE = TEST @Value(bridge) = yes
    TEST_MODE = TEST
    PASSED -> GeometryReplacer_Output
    PASSED -> wildlife_poly_bridges (writer GEOJSON_2)
    PASSED -> wildlife_poly_bridges (writer GEOJSON_1)
wildlife_poly_bridges (writer GEOJSON_1)
    attributes: accuracy string, ID_OSM int, fid int, osm_id string, bridge string, in_data string
GeometryReplacer_Output: Inspector [off]
wildlife_poly_bridges (writer GEOJSON_2)
    attributes: osm_id string, bridge string, in_data string, accuracy string, ID_OSM int, fid int

Bookmark: Verschnitt mit bestehenden digitalisierten Objekten
GeometryExtractor
    ATTR = _geometry
    KIND = fmebinary
    REMOVE_GEOMETRY = No
    KIND_LONG = FME Binary
    -> CenterPointReplacer
CenterPointReplacer
    POINTTYPE = CENTER
    POINT -> PointOnAreaOverlayer_3 [POINT]
digitized_overpasses (reader OGCGEOPACKAGE_1)
    attributes: accuracy text(255), ID_OSM mediumint, fid int,PrimaryKey
    -> Bufferer
    -> wildlife_poly_bridges (writer GEOJSON_1)
Bufferer
    ANGLE = 22.5
    CAP_STYLE_LOOKUP = CAP_ARC
    CORNER_STYLE_LOOKUP = JOIN_ARC
    MODE = AREA
    OFFSET = 300
    OFFSET_UNITS = NONE
    PRECISION = APPROX
    CAP_STYLE = Arc
    CORNER_STYLE = Arc
    BUFFERED -> AttributeCreator_2
AttributeCreator_2
    ATTR_TABLE = SET_TO in_data (varchar(3)) = yes
    -> PointOnAreaOverlayer_2 [AREA]
PointOnAreaOverlayer_2
    ATTR_ACCUM_MODE = HANDLE_CONFLICT
    ATTR_CONFLICT_RES = ORIGINAL_IF_CONFLICT
    DEAGGREGATE_INPUT = Yes
    OV_ATTR = _overlaps
    POLYS_FIRST = NO
    POINT -> Tester_3
Tester_3
    BOOL_OP = OR
    TEST_CLAUSE = TEST @Value(in_data) = yes
    TEST_MODE = TEST
    FAILED -> PointOnAreaOverlayer [POINT]

Bookmark: Objekte in CH ausschliessen
Landesgrenze (reader FILEGDB_1)
    attributes: OBJECTID objectid, xtf_id text(20), Gueltigkeit text(20), SHAPE_Length double
    -> Reprojector_2
Reprojector_2
    DEST = EPSG:3035
    INTERPOLATION_TYPE = NearestNeighbor
    RASTER_CELL_SIZE = PreserveCells
    RASTER_TOLERANCE = 0.0
    REPROJECTED -> PointOnAreaOverlayer_3 [AREA]
PointOnAreaOverlayer_3
    DEAGGREGATE_INPUT = Yes
    OV_ATTR = _overlaps
    POLYS_FIRST = NO
    POINT -> Tester_4
Tester_4
    BOOL_OP = OR
    TEST_CLAUSE = TEST @Value(_overlaps) != 1
    TEST_MODE = TEST
    PASSED -> PointOnAreaOverlayer_2 [POINT]

Bookmark: BBOX Europa im EPSG:3035
Creator
    GEOM = <?xml version="1.0" encoding="US_ASCII" standalone="no" ?><geometry><polygon><line><coord x="1908523.29" y="1137678.21"/><coord x="6901611.5" y="1137678.21"/><coord x="6901611.5" y="6872461.46"/><coord x="1908523.29" y="6872461.46"/><coord x="1908523.29" y="1137678.21"/></line></polygon></geometry>
    GEOMTYPE = Geometry Object
    NUM = 1
    CREATED -> CoordinateSystemSetter
CoordinateSystemSetter
    COORDSYS = EPSG:3035
    -> AttributeCreator
AttributeCreator
    ATTR_TABLE = SET_TO europa (varchar(3)) = yes
    -> PointOnAreaOverlayer [AREA]
